[DOCUMENT]
TITLE: System requirements
VERSION: @GIT_BRANCH

[TEXT]
STATEMENT: >>>
Architecture A has been chosen (seen below)

.. image:: ./_assets/STM32_opt1.svg
<<<

[[SECTION]]
TITLE: System requirements

[[/SECTION]]
