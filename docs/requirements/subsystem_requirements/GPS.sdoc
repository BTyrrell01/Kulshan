[DOCUMENT]
TITLE: Electrical Subsystem: GPS
VERSION: @GIT_BRANCH

[TEXT]
STATEMENT: >>>
**Scope**: The GPS subsystem includes the GPS and the GPS antenna.

GPS: Used to report the location in 3d space of the user.
<<<

[[SECTION]]
TITLE: Requirements

[REQUIREMENT]
UID: REQ-6
STATUS: Active
TITLE: GPS sample rate
STATEMENT: >>>
The GPS should refresh at a rate of at least 10hz
<<<
RELATIONS:
- TYPE: Parent
  VALUE: MOE-001-017

[REQUIREMENT]
UID: REQ-16
STATUS: Active
TITLE: GPS Accuracy
STATEMENT: >>>
The GPS accuracy have an absolute accuracy better than at least 1.5m
<<<
RELATIONS:
- TYPE: Parent
  VALUE: MOE-001-016

[[/SECTION]]
