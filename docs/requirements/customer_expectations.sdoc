[DOCUMENT]
TITLE: Stakeholder expectations for Kulshan sports watch
VERSION: @GIT_BRANCH

[TEXT]
STATEMENT: >>>
You can find more information on NGOs and MOEs in the NASA systems engineering handbook. Each requirement here is essentially an MOE, and the NGO is written as the rationale.
<<<

[[SECTION]]
TITLE: Stakeholder expectations

[REQUIREMENT]
UID: MOE-001-001
STATEMENT: The watch shall stay in place for a 10km run, withstand sweat and rain, and weigh less than 100g.
RATIONALE: The user can wear the watch all day, including during exercise, without it coming loose, falling off, or causing discomfort.

[REQUIREMENT]
UID: MOE-001-002
STATEMENT: >>>
The watch shall be able to stream to bluetooth classic devices for 18hrs, and be able to record an activity of at least 27:07 hours in length. Maximum current consumption at worst case must be no greater than 45mA. Activity modes without bluetooth should be around 25mA.
<<<
RATIONALE: >>>
The user should be able to stream bluetooth audio from the watch all day without being connected to a phone.
<<<
COMMENT: >>>
Under requirement MOE-001-002, to stream 18hrs of music, and remain alive for a full 27:07 hours

Current consumption https://www.desmos.com/calculator/0ouph6ei09
<<<

[REQUIREMENT]
UID: MOE-001-003
STATEMENT: The watch shall measure heart rate with a mean absolute error of no more than 10 bpm relative to an ECG chest-strap reference, for heart rates from 40 to 210 bpm, for users across Fitzpatrick skin types I–VI.
RATIONALE: The user can monitor their heartrate during activities regardless of the user.

[REQUIREMENT]
UID: MOE-001-004
STATEMENT: All user functions shall be achievable using only the watch and a supported phone or wireless network.
RATIONALE: Mechanical cables and pins are susceptible to mechanical failures.

[REQUIREMENT]
UID: MOE-001-005
STATEMENT: The watch shall not suffer mechanical damage in any way from a drop of 2m. The watch shall not be damaged from sunscreen, chlorine or saltwater. The watch should mechanically survive from -48C to 48C.
RATIONALE: The watch should be tough, and the user should not worry about breaking it during sports activities

[REQUIREMENT]
UID: MOE-001-006
STATEMENT: >>>
The watch should charge from 0% SOC to 100% SOC in 60 minutes.
<<<
RATIONALE: >>>
Some athletes have more than 1 activity in the day. The watch should be able to support this.
<<<
COMMENT: >>>
Fast charging is useful for:
* Multi-day trips where you need to charge the watch during a break
* The user doesn't have much time before the start of their activity, and they need the watch to survive the duration of the activity
<<<

[REQUIREMENT]
UID: MOE-001-007
STATEMENT: The watch should have a BoM cost of less than $250.
RATIONALE: The watch should be affordable to the target customers.

[REQUIREMENT]
UID: MOE-001-008
STATEMENT: The watch shall register start, stop, and lap commands on the first attempt in at least 99% of attempts when operated with bare hands coated with fresh water, sweat, pool water, and while wearing gloves that are 10mm thick.
RATIONALE: Some activities happen in the water or in the snow. The watch must be usable in these extreme conditions.

[REQUIREMENT]
UID: MOE-001-009
STATEMENT: The watch shall have replaceable straps. A service technician shall be able to take apart the device for root cause without causing permanent damage to the device.
RATIONALE: Customers should not have to purchase a new watch if there are small mechanical or cosmetic imperfections with the product.

[REQUIREMENT]
UID: MOE-001-010
STATEMENT: The watch shall record heart rate at intervals of no more than 1 second during a recorded activity.
RATIONALE: Some activities have very high heart rate variability, and the watch should be able to provide relevant heart rate information during those activities.

[REQUIREMENT]
UID: MOE-001-011
STATEMENT: >>>
The watch shall measure SPO2 with a mean absolute error of no more than 5% relative to a reference, for SPO2 from 80% to 100%, for users across Fitzpatrick skin types I–VI.
<<<
RATIONALE: >>>
Athletes train with a huge variation in SPO2. It is important to monitor SPO2 in the event that it gets too low.
<<<

[REQUIREMENT]
UID: MOE-001-012
STATEMENT: >>>
The watch shall record SPO2 at intervals of no more than 1 second during a recorded activity.
<<<
RATIONALE: >>>
SPO2 is a very important metric and should be monitored rapidly in the event it gets too low.
<<<

[REQUIREMENT]
UID: MOE-001-014
STATEMENT: >>>
The watch shall interface wirelessly with an app on iPhone/Android devices.
<<<
RATIONALE: >>>
Data should come off of the watch and be analyzable on a computer/phone.
<<<

[REQUIREMENT]
UID: MOE-001-015
STATEMENT: >>>
The watch should not suffer mechanical damage from depths of <= 30m in water. It should have a rating of at least IPX8.
<<<
RATIONALE: >>>
Swimming athletes might reach shallow depths in the water.
<<<

[REQUIREMENT]
UID: MOE-001-016
STATEMENT: The watch shall record the users location down to 1.5m accuracy.
RATIONALE: Accurate tracking of the athlete is central to knowing other very important metrics such as covered distance, speed, pace and many others.

[REQUIREMENT]
UID: MOE-001-017
STATEMENT: >>>
The watch shall update the users location while recording at a minimum of 10hz.
<<<
RATIONALE: >>>
Users could be traveling at a huge variety of speeds. The watch should report accurate distance regardless of user speed.
<<<

[REQUIREMENT]
UID: MOE-001-018
STATEMENT: >>>
The watch shall be able to alert the user with sound of at least 40dB intensity, as well as vibrate with an intensity of at least 0.1G.
<<<
RATIONALE: >>>
The user should be alerted when the athlete passes through an important distance or time goal/marker.
<<<

[REQUIREMENT]
UID: MOE-001-019
STATEMENT: The watch shall measure altitude with a mean absolute error of no more than 10m.
RATIONALE: For outdoor activities in the mountains, it is essential to have accurate altitude information available.

[REQUIREMENT]
UID: MOE-001-020
STATEMENT: >>>
The watch shall count the steps of the user, with a mean error of no more than 1ppm.
<<<
RATIONALE: >>>
Running athletes use cadence as a metric for monitoring running form, the watch should report running spm and total steps each day.
<<<

[REQUIREMENT]
UID: MOE-001-021
STATEMENT: >>>
The watch shall be able to store 18hrs worth of audio in the form of 192kbps AAC audio internally
<<<
RATIONALE: >>>
The user should be able to stream bluetooth audio from the watch all day without being connected to a phone.
<<<

[REQUIREMENT]
UID: MOE-001-022
STATUS: Active
STATEMENT: >>>
The device should securely boot, upgrade/update, and transfer data to the users devices.
<<<
RATIONALE: >>>
The device should not reveal any user data or device firmware to the outside world or attackers.
<<<

[[/SECTION]]
